FME workspace ISU Elektra 01.fmw
Title: ISU Elektra 1 / Teruglevering, DM_GEO_PROJECTEN@AINPC1 + DM_ESRI@AADWH2 -> DM_GEO_PROJECTEN@AINPC1

Parameters:
- DM_GEO_PROJECTEN = \\geonas\geo_analysis\AGENT\GIS_connecties\acceptatie beheer\DC - AINPC1 - DM_GEO_PROJECTEN.sde   # Connection File
- DM_ESRI = \\geonas\geo_analysis\AGENT\GIS_connecties\acceptatie beheer\DC - AADWH2 - DM_ESRI.sde   # Connection File

Readers:
- GEODATABASE_SDE_1: GEODATABASE_SDE
- GEODATABASE_SDE_2: GEODATABASE_SDE

Writers:
- GEODATABASE_SDE_3: GEODATABASE_SDE

Note: Replace with view / productgroep = 'E'
GIS_ISU_AANSLUITINGEN (reader GEODATABASE_SDE_2)
    attributes: DATUM_AANLEG date, INSTALLATIE char(10), SOORT_INSTALLATIE char(4), VANAF_DATUM date, EIND_DATUM date, EAN_CODE char(50), OPNAME_EENHEID char(40), GAS_DRUK_NIVEAU char(2), SPANNINGSNIVEAU char(40), FYSIEKE_STATUS char(3), DUURZAME_ENERGIE char(3), TERUGLEVERCAPACITEIT double, LEVERINGSRICHTING char(3), BESTURING_AANT_TOEGEST char(8), PRODUCTGROEP char(2), PROFIELCATEGORIE char(3), TARIEFTYPE char(10), TARIEFTYPE_OMSCHR char(60), VERBLIJFSFUNCTIE char(2), VERBLIJFSFUNCTIE_OMSCHR char(20), GEBRUIK_AANSLUITING char(60), FYSIEKE_CAPACITEIT char(5), GV_KV char(3), INSTALLATIE_SOORT char(3), KEY_HOOFD_INSTALLATIE char(10), LEVERINGS_RICHTING char(3), OPANAME_EENHEID char(8), STRAAT char(60), HUISNUMMER char(10), HUISNUMMER_TOEVOEGING char(10),
      POSCODE char(10), PLAATS char(40), NUMMER_ZAKENPARTNER char(10), CONTRACT char(10), PERIODE_VERBRUIK_LAAG double, PERIODE_VERBRUIK_NORM double, EXTERN_NUMMER char(20), MAATEENHEID char(3), CONTRACT_CAPACITEIT double
    -> FeatureMerger [REQUESTOR]
Note: ACTUEEL = 'J'
E_LS_LEVERINGSPUNT_PRI_2RP (reader GEODATABASE_SDE_1)
    attributes: ESRI_ID integer, ASSET_NETWERK_NAAM char(30), ASSET_NETWERK_ID double, AANDUIDING char(100), AARDING char(4000), BEVEILIGINGSWAARDE char(4000), BRON_ID double, CAPACITEIT char(100), CATEGORIE_AANSLUITING char(100), DATUM_AANSLUITING date, DOORSNEDE char(100), EAN_CODE char(100), FABRIKAAT_AFTAKMOF char(100), FABRIKANT_AANSLUITKAST char(100), GEBRUIK_AANSLUITING char(100), GECONTRACTEERD_VERMOGEN double, HUISNR_TOEVOEGING char(100), HUISNUMMER char(100), HULPADERS_JN char(4000), IND_BEMETERD char(1000), KABELTYPE char(4000), LENGTE_KABEL double, LEVERINGSRICHTING char(100), MATERIAALSOORT char(100), MATERIAAL_AANSLUITKAST char(4000), MAX_NOMINALE_SPANNING char(4000), MAX_STROOMSTERKTE double, METERNUMMER char(100), MIN_NOMINALE_SPANNING char(4000), MUTATIE_DATUM_CAR date,
      OPMERKINGEN char(4000), OPVOER_DATUM date, ORUIM_JN char(100), PASVORM char(100), PLAATS char(100), POSTCODE char(100), PROFIELCATEGORIE char(100), PROJECTNUMMER char(100), SCHAKELWIJZE char(100), SCHETS char(4000), SCHETSNUMMER char(100), SOORT char(4000), SOORT_AFTAKMOF char(100), SOORT_KLEMMEN char(4000), STANDAARD_JAARVERBRUIK_DAL double, STANDAARD_JAARVERBRUIK_PLATEAU double, STATUS_AANSLUITING char(100), STATUS_BEHEER char(4000), STRAATNAAM char(100), TYPE_AANSLUITKAST char(100), TYPE_AFTAKKLEM char(100), TYPE_AFTAKMOF char(100), TYPE_METER char(100), USER_ID char(100), WIJZIG_DATUM date, MERIDIAN_URL char(119), GELDIG_VAN date, GELDIG_TOT date, ACTUEEL char(1), WORKFLOW_ID double,
      PROCES_CODE char(30), LAAD_DATUM date, SE_ANNO_CAD_DATA blob
    -> FeatureMerger [SUPPLIER]
Note: Get geometry from leveringspunt_pri / If there is no geometry match, then try leveringspunt_sec
FeatureMerger
    CLEANING_TOLERANCE = Automatic
    JOIN_KEYS = @Value(EAN_CODE) @Value(EAN_CODE) AUTO
    MERGE_TYPE = Geometry
    PROCESS_DUPS = No
    REJECT_NULL_MISSING_KEYS = No
    SUPPLIERS_FIRST = Yes
    MERGED -> GIS_ISU_AANSLUITINGEN_E (writer GEODATABASE_SDE_3)
    UNMERGED_REQUESTOR -> FeatureMerger_2 [REQUESTOR]
    <REJECTED> -> FeatureMerger__Rejected_
FeatureMerger__Rejected_: Logger
    MAXCOORDS = 20
    MAXFEATS = 20
    MESSAGE = Feature is:
Note: ACTUEEL = 'J'
E_LS_LEVERINGSPUNT_SEC_2RP (reader GEODATABASE_SDE_1)
    attributes: ESRI_ID integer, ASSET_NETWERK_NAAM char(30), ASSET_NETWERK_ID double, AANDUIDING char(100), AARDING char(4000), BEVEILIGINGSWAARDE char(4000), BRON_ID double, CAPACITEIT char(100), CATEGORIE_AANSLUITING char(100), DATUM_AANSLUITING date, DOORSNEDE char(100), DOORSNEDE_AARDSCHERM char(100), EAN_CODE char(100), FABRIKAAT char(100), FABRIKANT_AANSLUITKAST char(100), GEBRUIK_AANSLUITING char(100), GECONTRACTEERD_VERMOGEN double, HUISNR_TOEVOEGING char(100), HUISNUMMER char(100), HULPADERS_JN char(4000), IND_BEMETERD char(1000), KABELTYPE char(4000), LENGTE_KABEL double, LEVERINGSRICHTING char(100), MATERIAALSOORT char(100), MATERIAAL_AANSLUITKAST char(4000), MAX_NOMINALE_SPANNING char(4000), MAX_STROOMSTERKTE double, METERNUMMER char(100), MIN_NOMINALE_SPANNING char(4000),
      MUTATIE_DATUM_CAR date, OPMERKINGEN char(4000), OPVOER_DATUM date, ORUIM_JN char(100), PASVORM char(100), PLAATS char(100), POSTCODE char(100), PROFIELCATEGORIE char(100), RICHTING_AANSLUITKABEL char(4000), SCHAKELWIJZE char(100), SOORT char(4000), STANDAARD_JAARVERBRUIK_DAL double, STANDAARD_JAARVERBRUIK_PLATEAU double, STATUS_AANSLUITING char(100), STRAATNAAM char(100), TYPE_AANSLUITKAST char(100), TYPE_METER char(100), USER_ID char(100), VERDIEPING double, WIJZIG_DATUM date, ASSET_NETWERK_ID_PRI double, ASSET_NETWERK_NAAM_PRI char(30), GELDIG_VAN date, GELDIG_TOT date, ACTUEEL char(1), WORKFLOW_ID double, PROCES_CODE char(26), LAAD_DATUM date, SE_ANNO_CAD_DATA blob
    -> FeatureMerger_2 [SUPPLIER]
Note: Get geometry from leveringspunt_sec
FeatureMerger_2
    CLEANING_TOLERANCE = Automatic
    JOIN_KEYS = @Value(EAN_CODE) @Value(EAN_CODE) AUTO
    MERGE_TYPE = Geometry
    PROCESS_DUPS = No
    REJECT_NULL_MISSING_KEYS = No
    SUPPLIERS_FIRST = No
    MERGED -> GIS_ISU_AANSLUITINGEN_E (writer GEODATABASE_SDE_3)
    <REJECTED> -> FeatureMerger_2__Rejected_
Note: geocoded SAP ISU aansluitingen
GIS_ISU_AANSLUITINGEN_E (writer GEODATABASE_SDE_3)
    attributes: DATUM_AANLEG date, INSTALLATIE char(10), SOORT_INSTALLATIE char(4), VANAF_DATUM date, EIND_DATUM date, EAN_CODE char(50), OPNAME_EENHEID char(40), GAS_DRUK_NIVEAU char(2), SPANNINGSNIVEAU char(40), FYSIEKE_STATUS char(3), DUURZAME_ENERGIE char(3), TERUGLEVERCAPACITEIT double, LEVERINGSRICHTING char(3), BESTURING_AANT_TOEGEST char(8), PRODUCTGROEP char(2), PROFIELCATEGORIE char(3), TARIEFTYPE char(10), TARIEFTYPE_OMSCHR char(60), VERBLIJFSFUNCTIE char(2), VERBLIJFSFUNCTIE_OMSCHR char(20), GEBRUIK_AANSLUITING char(60), FYSIEKE_CAPACITEIT char(5), GV_KV char(3), INSTALLATIE_SOORT char(3), KEY_HOOFD_INSTALLATIE char(10), LEVERINGS_RICHTING char(3), OPANAME_EENHEID char(8), STRAAT char(60), HUISNUMMER char(10), HUISNUMMER_TOEVOEGING char(10),
      POSCODE char(10), PLAATS char(40), NUMMER_ZAKENPARTNER char(10), CONTRACT char(10), PERIODE_VERBRUIK_LAAG double, PERIODE_VERBRUIK_NORM double, EXTERN_NUMMER char(20), MAATEENHEID char(3), CONTRACT_CAPACITEIT double
FeatureMerger_2__Rejected_: Logger
    MAXCOORDS = 20
    MAXFEATS = 20
    MESSAGE = Feature is:

Bookmark: Elektra
Note: Verwerking Elektra data
